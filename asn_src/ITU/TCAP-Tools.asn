-- Module TCAP-Tools (Q.775:06/1997)
TCAP-Tools {itu-t(0) recommendation(0) q(17) 775 modules(2) tools(1) version1(1)}

DEFINITIONS ::= BEGIN

EXPORTS cancel, cancelFailed, cancelled;

IMPORTS
  OPERATION, ERROR
    FROM Remote-Operations-Information-Objects
        {joint-iso-itu-t(2) remote-operations(4) informationObjects(5) version1(0)};
--  TCInvokeIdSet
--    FROM TCAPMessages {itu-t recommendation q 773 modules(2) messages(1)
--      version3(3)};

cancel OPERATION ::= {
  -- ARGUMENT  present < TCInvokeIdSet
  ARGUMENT  INTEGER (-128..127)
  -- a TC-user may redefine this type to include
  -- an empty result so that it becomes a Class 1 operation
  ERRORS    {cancelFailed}
}

-- timer = 15 s
cancelFailed ERROR ::= {
  PARAMETER SET {
    problem   [0]  CancelProblem,
--    invokeId  [1]  present < TCInvokeIdSet
    invokeId  [1]  INTEGER (-128..127)
  }
  CODE  local:0
}

CancelProblem ::= ENUMERATED {unknownInvocation(0), tooLate(1), notCancellable(2)}

-- a TC-user may redefine this type to include application-specific problems
cancelled ERROR ::= {
  CODE      local:0
}

-- an error of this type should be included in the error list of cancellable operations
END
